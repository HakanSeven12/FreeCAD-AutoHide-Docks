"""
This macro makes by hides the FreeCAD docks (sidebars), by default. 
When the mouse moves towards them, they become visible.
"""

__Name__ = 'AutoHideDocks'
__Comment__ = 'FreeCAD docks are hidden by default until mouse scrolling activates them'
__Author__ = '@HakanSeven12'
__Version__ = '0.3'
__Date__ = '2020-03-29'
__License__ = 'LGPL2.1'
__Web__ = ''
__Wiki__ = ''
__Icon__ = ''
__Help__ = 'https://forum.freecadweb.org/viewtopic.php?f=22&t=44659'
__Status__ = 'Beta'
__Requires__ = 'FreeCAD V0.18+'
__Communication__ = 'https://github.com/HakanSeven12/FCAutoHide'
__Files__ = ''


from PySide2 import QtCore, QtGui, QtWidgets

class autoHide(QtCore.QObject):
    side = False
    docked = True
    AHEnable = 0
    target = None
    AHD = None

    def __init__(self, dock, AHD):
        super(autoHide, self).__init__(dock)
        dock.installEventFilter(self)
        AHD.installEventFilter(self)
        self.visible = dock.features()
        self.orgHeight = dock.sizeHint().height()
        self.orgWidth = dock.sizeHint().width()
        area = mv.dockWidgetArea(dock)
        self.collapsedDock(dock, area)
        self.target = dock
        self.AHD = AHD

    def eventFilter(self, source, event):
        area = mv.dockWidgetArea(self.target)
        if (source is self.AHD) and (event.type() is event.MouseButtonPress):
            self.AHEnable = (self.AHEnable + 1) % 2

            if self.AHEnable:
                self.openDock(self.target)
                self.target.removeEventFilter(self)
            else:
                self.collapsedDock(self.target, area)
                self.target.installEventFilter(self)

        elif source is self.target:
            if (event.type() is event.Enter) or \
                (self.target.isFloating() and self.docked):
                for dockWid in mv.findChildren(QtWidgets.QDockWidget):
                    if dockWid.isVisible and (mv.dockWidgetArea(dockWid) is area):
                        self.openDock(dockWid)
                return True

            elif event.type() is event.Leave:
                for dockWid in mv.findChildren(QtWidgets.QDockWidget):
                    if dockWid.isVisible and (mv.dockWidgetArea(dockWid) is area):
                        self.collapsedDock(dockWid, area)
                return True

        return super(autoHide, self).eventFilter(source, event)

    def openDock(self, dock):
        dock.setMaximumSize(5000, 5000)
        dock.setFeatures(self.visible)
        self.docked = False
        self.modifyDock(dock, self.orgWidth, self.orgHeight)


    def collapsedDock(self, dock, area):
        self.side = False
        self.docked = True
        dock.setMaximumSize(5000, 5000)

        if (area is QtCore.Qt.LeftDockWidgetArea) or \
            (area is QtCore.Qt.RightDockWidgetArea):
            self.side = True
            features = QtWidgets.QDockWidget.DockWidgetFeatures(
                self.visible | QtWidgets.QDockWidget.DockWidgetVerticalTitleBar)
            dock.setFeatures(features)

        try:
            TBHeight = dock.style().pixelMetric(
                QtWidgets.QStyle.PM_TitleBarHeight)
        except:
            TBHeight = 25
        self.modifyDock(dock, TBHeight, TBHeight)

    def modifyDock(self, dock, width, height):
        if self.side:
            dock.setFixedWidth(width)
        else:
            dock.setFixedHeight(height)
        dock.setSizePolicy(
            QtWidgets.QSizePolicy.Expanding, QtWidgets.QSizePolicy.Expanding)

mv = FreeCADGui.getMainWindow()
AHD = QtWidgets.QPushButton("AH")
mv.statusBar().addPermanentWidget(AHD)
mv.statusBar().setVisible(True)

for dock in mv.findChildren(QtWidgets.QDockWidget):
    autoHide(dock, AHD)

    """
    title_bar = QtWidgets.QWidget()
    layout = QtWidgets.QHBoxLayout()
    title_bar.setLayout(layout)
    button = QtWidgets.QToolButton()
    layout.addWidget(button)
    icon = dock.style().standardIcon(QtWidgets.QStyle.SP_TitleBarMaxButton, widget=dock)
    button.setIcon( icon )
    dock.setTitleBarWidget(title_bar)
    """
